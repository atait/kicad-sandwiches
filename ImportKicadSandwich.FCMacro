# -*- coding: utf-8 -*-
''' Imports three kicad sandwich boards and stacks them up in a new document
    You will have to hit enter a few times to deal with messages from KicadStepup
    Now also works with VRMLs exported from kicad

    To install,
    1. copy this file to ~/.FreeCAD/Macro/ (Linux) or ~/Library/Application Support/FreeCAD/Macro/ (Mac)
    2. Install KicadStepUp through the package manager.
    3. Add a toolbar item following instructions here https://wiki.freecadweb.org/Macros
'''
import os
import FreeCAD
import kicadStepUptools
from PySide import QtGui


# --- helper functions ---

def select_files():
    # Figure out the files of either kicad_pcb or wrl formats
    mFile, _ = QtGui.QFileDialog.getOpenFileName(None, 'Select any of the sandwich boards', None, '*.kicad_pcb *.wrl')
    root_dir = os.path.dirname(mFile)
    selected_basename, extension = os.path.splitext(os.path.basename(mFile))
    use_stepup = extension == '.kicad_pcb'
    sandwich_group = '-'.join(selected_basename.split('_')[:-1])
    sandwich_suffixes = ['LOW', 'MID', 'TOP']
    file_fmt = os.path.join(root_dir, sandwich_group + '_{}' + extension)
    files = [file_fmt.format(suffix) for suffix in sandwich_suffixes]
    if not os.path.exists(files[1]):  # It is 2-board
        sandwich_suffixes.pop(1)
        files.pop(1)
    for file in files:
        if not os.path.exists(file):
            raise IOError('Did not find kisandwich file: ' + file)
    docnames = [sandwich_group.replace('-', '_') + '_{}'.format(suffix) for suffix in sandwich_suffixes]
    return files, docnames, use_stepup


def open_stepup_pcbs(files):
    # Open the boards and get the actual names of document and parts
    board_partnames = [None] * len(files)
    actual_docnames = [None] * len(files)
    for i in range(len(files)):
        print('Opening', files[i])
        kicadStepUptools.open(files[i])
        actual_docnames[i] = App.activeDocument().Name  # Sometimes it is different for uniqueness
        objs = FreeCAD.ActiveDocument.Objects
        for ob in objs:
            if ob.Label.startswith('Board_Geoms') and ob.Name.startswith('Board_Geoms'):
                suffix = ob.Name.split('_')[-1]
                actual_part_label = 'Board_' + suffix
                board_partnames[i] = actual_part_label
                break
        else:
            raise TypeError('Could not find a part starting with "Board_Geoms"')
    return actual_docnames, board_partnames


def consolidate_pcbs(stack_doc, src_docnames, partnames):
    # Copy each board model into the assembled document
    def activate_window(docname):
        App.setActiveDocument(docname)
        App.ActiveDocument=App.getDocument(docname)
        Gui.ActiveDocument=Gui.getDocument(docname)

    for i in range(3):
        activate_window(src_docnames[i])
        Gui.Selection.addSelection(src_docnames[i], partnames[i])
        Gui.runCommand('Std_Copy',0)

        activate_window(stack_doc)
        Gui.runCommand('Std_Paste', 0)
        Gui.Selection.clearSelection()


def stack_parts(stack_doc, partnames, pitch=2):
    # Stack up the boards
    def offset_part(mm):
        return App.Placement(App.Vector(0,0,mm),App.Rotation(App.Vector(0,0,1),0))

    for i in range(len(partnames)):
        embedded_part = FreeCAD.getDocument(stack_doc).getObject(partnames[i])
        embedded_part.Placement = offset_part(i * pitch)


# --- primary import scripts ---

def import_vrml_pcbs(files, partnames):
    # There is an assumption that the docnames are the same as partnames
    App.newDocument("Sandwich_VRML")
    stack_doc = App.activeDocument().Name
    for i in range(len(files)):
        FreeCADGui.insert(files[i], stack_doc)
    stack_parts(stack_doc, partnames)


def import_stepup_pcbs(files, docnames):
    # docnames is not used because we verify their actual names after import
    actual_docnames, board_partnames = open_stepup_pcbs(files)
    App.newDocument("Sandwich_StepUp")
    stack_doc = App.activeDocument().Name
    consolidate_pcbs(stack_doc, actual_docnames, board_partnames)
    stack_parts(stack_doc, board_partnames)


# --- macro begins here ---

files, docnames, use_stepup = select_files()
if use_stepup:
    import_stepup_pcbs(files, docnames)
else:
    import_vrml_pcbs(files, docnames)

# Visualization
Gui.activeDocument().activeView().viewIsometric()
Gui.SendMsgToActiveView("ViewFit")
